// Merged SysML v2 Examples
// Generated by SysMLv2CheatSheet Generator

// --- Source: ActionPatterns_1WhileLoop.sysml ---
package WhileLoopExample {
    private import ScalarValues::*;
    action def Main {
        attribute x : Integer = 0;
        action loopAction {
            while x < 10 {
                assign x := x + 1;
            }
        }
    }
    view LoopView {
        expose Main;
    }
}

// --- Source: ActionPatterns_2ForLoop.sysml ---
package ForLoopExample {
    private import ScalarValues::*;
    action def Main {
        action process { in i : Integer; }
        action loopAction {
            for i in 1..10 {
                perform process { in i = i; }
            }
        }
    }
    view LoopView {
        expose Main;
    }
}

// --- Source: ActionPatterns_2bLoopVariations.sysml ---
package LoopVariationsExample {
    private import ScalarValues::*;
    attribute def Power;
    attribute profile : Power[*];
    action def Main {
        attribute x : Integer = 0;
        attribute done : Boolean = false;
        
        action collectionLoop {
            for p : Power in profile {
                /* body */
            }
        }
        
        action whileUntilLoop {
            while x < 10 {
                assign x := x + 1;
            } until done;
        }
        
        action infiniteLoop {
            loop {
               assign x := x + 1;
            } until x > 100;
        }
    }
    view LoopView {
        expose Main;
    }
}

// --- Source: ActionPatterns_3IfElse.sysml ---
package ActionPatterns_3IfElse {
    private import ScalarValues::*;
    private import SysML::*;
    action def Main {
        attribute x : Integer = 0;
        attribute y : Integer;
        if x > 0 {
           assign y := 1;
        } else {
           assign y := 0;
        }
    }
    view ExposeExample { expose Main; }
}

// --- Source: ActionPatterns_4AcceptVariations.sysml ---
package ActionPatterns_4AcceptVariations {
    private import ScalarValues::*;
    private import SysML::*;
    action def Main {
        attribute temp : Real;
        attribute s : Real;
        part schedule;
        action def StartSignal;
        action acceptSomething {
            accept startSignal : StartSignal;
            doc /* about startSignal ... */
            accept when temp > 100;
            accept at schedule;
            accept after 10 [s];
        }
    }
    view ExposeExample { expose Main; }
}

// --- Source: ActionPatterns_5SendVariations.sysml ---
package ActionPatterns_5SendVariations {
    private import ScalarValues::*;
    private import SysML::*;
    action def Main {
        action def StartSignal;
        part p1;
        attribute sig : StartSignal;
        action sendA { send sig via p1; }
        send sig via p1;
        doc /* Named vs Unnamed */
    }
    view ExposeExample { expose Main; }
}

// --- Source: ActionPatterns_6ControlNodes.sysml ---
package ActionPatterns_6ControlNodes {
    private import ScalarValues::*;
    private import SysML::*;
    
    action def Main {
        /* 1. Fork: Outgoing target mult 1..1 */
        fork f1;
        
        /* 2. Join: Incoming source mult 1..1 */
        join j1;
        
        /* 3. Decide: Outgoing target mult 0..1 (Optional) */
        decide d1;
        
        /* 4. Merge: Incoming source mult 0..1 (Optional) */
        merge m1;
    }

    view ExposeExample {
        expose Main;
    }
}

// --- Source: ActionPatterns_7AdvancedSend.sysml ---
package ActionPatterns_7AdvancedSend {
    private import ScalarValues::*;
    private import ScalarValues::*;
    private import SysML::*;
    private import Base::*;
    action def Main {
        attribute val : Anything;
        part monitor;
        action sendReading send {
           in payload;
           in sender = monitor;
        }
        flow val to sendReading.payload;
    }
    view ExposeExample { expose Main; }
}

// --- Source: Actions_1ActionDefinition.sysml ---
package Actions_1ActionDefinition {
    private import ScalarValues::*;
    private import SysML::*;
    attribute def Speed;
    attribute def Result;
    action def Serve {
       in speed : Speed;
       out result : Result;
       first toss;
       then strike;
       action toss;
       action strike;
    }
}

// --- Source: Actions_2ActionUsage.sysml ---
package Actions_2ActionUsage {
    private import ScalarValues::*;
    private import SysML::*;
    action def Serve;
    action def Main {
        action playPoint {
           action serve : Serve;
           perform serve { /* ... */ }
           action serve2 : Serve;
           perform serve2;
        }
    }
    view ExposeExample { expose Main; }
}

// --- Source: Actions_4Parameters.sysml ---
package Actions_4Parameters {
    private import ScalarValues::*;
    private import SysML::*;
    action def ComputeValues {
       in x : Real;
       inout y : Real;
       out z : Real;
    }
}

// --- Source: Actions_5SendAcceptSignal.sysml ---
package Actions_5SendAcceptSignal {
    private import ScalarValues::*;
    private import SysML::*;
    package Signal { action def Stop; action def Resume; }
    action def Main {
        part pOut;
        part ctl;
        action communicate {
           attribute sig : Signal::Stop;
           send sig via pOut to ctl;
           accept Signal::Resume;
        }
    }
    view ExposeExample { expose Main; }
}

// --- Source: Actions_6Successionfirstthen.sysml ---
package Actions_6Successionfirstthen {
    private import ScalarValues::*;
    private import SysML::*;
    action def Main {
        action start;
        action process;
        action finish;
        first start;
        then process;
        then finish;
        doc /* Control flow sequence */
    }
    view ExposeExample { expose Main; }
}

// --- Source: Actions_7Assignmentassign.sysml ---
package Actions_7Assignmentassign {
    private import ScalarValues::*;
    action def Main {
        attribute x : Integer;
        attribute y : Integer;
        assign x := 42;
        assign y := x + 1;
        doc /* Value assignment */
    }
    view ExposeExample { expose Main; }
}

// --- Source: Actions_8Trigger.sysml ---
package Actions_8Trigger {
    private import ScalarValues::*;
    private import SysML::*;
    action def Main {
        action def Tick;
        part clock;
        attribute t : Real;
        accept tick : Tick via clock;
        accept when t > 10.0;
        doc /* Event trigger with guard */
    }
    view ExposeExample { expose Main; }
}

// --- Source: Actions_Tutorial.sysml ---
package Actions_Tutorial {
    private import ScalarValues::*;
    
    /* reusable action */
    action def LogStatus { in msg : String; }

    action def ProcessData {
        /* Defining steps */
        action step1;
        action step2;
        action step3;
        
        /* --- Control Flow --- */
        /* 'first' implies the entry point */
        first step1;
        
        /* 'then' implies succession (step1 completes before step2 starts) */
        flow from step1 to step2; /* explicit */
        
        /* Shorthand for flow: */
        /* step2 then step3;  */ 
        
        /* --- Parallelism --- */
        action branchA;
        action branchB;
        
        /* Forking: step3 triggers both branches */
        flow from step3 to branchA;
        flow from step3 to branchB;
        
        /* --- Using Definitions --- */
        action logger : LogStatus {
            in msg = "Processing Complete";
        }
        
        /* Joining: both must finish before logger runs */
        flow from branchA to logger;
        flow from branchB to logger;
    }
}

// --- Source: Allocation_Tutorial.sysml ---
package Allocation_Tutorial {
    
    /* --- Behavioral / Logical View --- */
    action def ComputePath;
    
    /* --- Physical / Structural View --- */
    part def FlightComputer;
    
    /* Create a dedicated package for allocations between usages */
    package AllocationContext {
        part ecu : FlightComputer;
        action plan : ComputePath;
        
        /* Allocate the action usage (plan) to the hardware usage (ecu) */
        /* Meaning: "The ECU executes the planning action" */
        allocate plan to ecu;
    }
}

// --- Source: Analysis_Tutorial.sysml ---
package Analysis_Tutorial {
    private import ScalarValues::*;
    
    /* --- 1. Constraint Definition --- */
    constraint def MassEquation {
        in total : Real;
        in p1 : Real;
        in p2 : Real;
        
        /* The math */
        total == p1 + p2
    }
    
    part def System {
        attribute mass : Real;
        attribute part1Mass : Real;
        attribute part2Mass : Real;
        
        /* --- 2. Constraint Usage (Parametrics) --- */
        /* Binding properties to the equation parameters */
        constraint massCheck : MassEquation {
            in total = mass;
            in p1 = part1Mass;
            in p2 = part2Mass;
        }
    }
    
    /* --- 3. Analysis Case --- */
    analysis def WeightCheck {
        subject system : System;
        
        /* Determining if mass is within limits */
        return result : Boolean = system.mass < 100.0;
    }
}

// --- Source: Behavior_1StateDefinition.sysml ---
package Behavior_1StateDefinition {
    private import ScalarValues::*;
    private import SysML::*;
    /* Wrapped Snippet (Structure Context) */
    state   def  PracticeSession  {
       entry ;  exit ;
       state  Idle ;
       state  Serving ;
    }
}

// --- Source: Behavior_2Transitions.sysml ---
package Behavior_2Transitions {
    private import ScalarValues::*;
    private import SysML::*;
    state def Main {
        state Idle;
        state Serving;
        action def Log { in msg : String; }
        action def Start;
        part Remote { action start : Start; }
        transition startServe
           first Idle
           accept Remote.start
           do action log : Log { in msg = 'Serving'; }
           then Serving;
    }
}

// --- Source: Behavior_3GuardsEffects.sysml ---
package Behavior_3GuardsEffects {
    private import ScalarValues::*;
    private import SysML::*;
    state def Main {
        state Green;
        state Red;
        attribute traffic : Integer;
        action resetTimer;
        transition t2 first Green if traffic == 0 do resetTimer then Red;
    }
}

// --- Source: Behavior_3bInternalTransition.sysml ---
package Behavior_3bInternalTransition {
    private import ScalarValues::*;
    private import SysML::*;
    state def Monitoring {
       state selfCheck;
       action def tick;
       action check;
       transition t1 first selfCheck accept tick do check then selfCheck;
    }
}

// --- Source: Behavior_4ActionDefinition.sysml ---
package Behavior_4ActionDefinition {
    private import ScalarValues::*;
    private import SysML::*;
    attribute def Speed;
    attribute def Result;
    action def Serve {
       in speed : Speed;
       out result : Result;
       first toss;
       then strike;
       action toss;
       action strike;
    }
}

// --- Source: Behavior_5ActionUsage.sysml ---
package Behavior_5ActionUsage {
    private import ScalarValues::*;
    private import SysML::*;
    action def Serve { in speed : Integer; }
    /* Wrapped Snippet (Action Context) */
    action def Main {
        action  playPoint  {
           action  serve  :  Serve ;
           perform  serve  {
              in  speed  =  60 ;
           }
        }
    }

    view ExposeExample {
        expose Main;
    }
}

// --- Source: Behavior_6UseCases.sysml ---
package Behavior_6UseCases {
    private import ScalarValues::*;
    private import SysML::*;
    part def PickleBot;
    part def Player;
    use case def Practice {
       subject b : PickleBot;
       actor p : Player;
       objective {
          doc /* Improve skills */
       }
    }
}

// --- Source: Calculations_1CalculationDefinition.sysml ---
package Calculations_1CalculationDefinition {
    private import ScalarValues::*;
    private import SysML::*;
    attribute def Voltage;
    attribute def Current;
    attribute def Power;
    calc def PowerCalc {
       in v : Voltage;
       in i : Current;
       return p : Power = v * i;
    }
}

// --- Source: Calculations_2CalculationUsage.sysml ---
package Calculations_2CalculationUsage {
    private import ScalarValues::*;
    private import SysML::*;
    attribute def Voltage; attribute def Current; attribute def Power;
    calc def PowerCalc { in v : Voltage; in i : Current; return p : Power; }
    /* Wrapped Snippet (Action Context) */
    action def Main {
        calc  p_motor  :  PowerCalc  {
           in  v  =  12.0 ;
           in  i  =  5.0 ;
        }
    }

    view ExposeExample {
        expose Main;
    }
}

// --- Source: Calculations_4ConstraintUsage.sysml ---
package Calculations_4ConstraintUsage {
    private import ScalarValues::*;
    private import SysML::*;
    attribute def Mass;
    constraint def MassLimit { in m : Mass; in limit : Mass; }
    /* Wrapped Snippet (Action Context) */
    action def Main {
        attribute mass : Mass;
        constraint  checkMass  :  MassLimit  {
           in  m  =  mass ;
           in  limit  =  1000.0 ;
        }
    }

    view ExposeExample {
        expose Main;
    }
}

// --- Source: Calculations_5Assertions.sysml ---
package Calculations_5Assertions {
    private import ScalarValues::*;
    private import SysML::*;
    action def Main {
        attribute x : Integer;
        attribute y : Integer;
        assert constraint {
           x > 0
        }
        assert constraint {
           not (y < 0)
        }
    }
    view ExposeExample { expose Main; }
}

// --- Source: Calculations_6Requirements.sysml ---
package Calculations_6Requirements {
    private import ScalarValues::*;
    private import SysML::*;
    requirement def Safety {
       attribute temp : Real;
       attribute pressure : Real;
       assume constraint { temp < 100 }
       require constraint { pressure < 50 }
    }
}

// --- Source: Cases_1UseCaseDefinition.sysml ---
package Cases_1UseCaseDefinition {
    private import ScalarValues::*;
    private import SysML::*;
    attribute def Vehicle;
    attribute def Person;
    /* Wrapped Snippet (Structure Context) */
    use   case   def  DriveCar  {
        subject  vehicle  :  Vehicle ;
        actor  driver  :  Person ;
        objective  {
           doc  /* Transport safely */
        }
    }
}

// --- Source: Cases_2TestCaseVerification.sysml ---
package Cases_2TestCaseVerification {
    private import ScalarValues::*;
    private import SysML::*;
    attribute def Vehicle;
    attribute def Person;
    attribute def VerdictKind;
    /* Wrapped Snippet (Structure Context) */
    requirement brakeReq;
    requirement stoppingDistance;
    verification   def  TestBrakes  {
       objective {
           verify  brakeReq ;
           verify  stoppingDistance ;
       }
       return  verdict  :  VerdictKind ;
    }
}

// --- Source: Cases_3AnalysisCase.sysml ---
package Cases_3AnalysisCase {
    private import ScalarValues::*;
    private import SysML::*;
    attribute def Vehicle;
    /* Wrapped Snippet (Structure Context) */
    analysis   def  FuelEconomy  {
       subject  vehicle  :  Vehicle ;
       objective  {
          doc  /* Estimate MPG */
       }
       return  mpg  :  Real ;
    }
}

// --- Source: Cases_4CaseUsage.sysml ---
package Cases_4CaseUsage {
    private import ScalarValues::*;
    private import SysML::*;
    attribute def Vehicle; attribute def Person;
    use case def DriveCar { subject vehicle : Vehicle; actor driver : Person; }
    part me : Person;
    /* Wrapped Snippet (Structure Context) */
    use   case  driveToWork  :  DriveCar  {
       actor  driver  =  me ;
    }
}

// --- Source: Connections_1ConnectionDefinition.sysml ---
package Connections_1ConnectionDefinition {
    private import ScalarValues::*;
    private import SysML::*;
    part def Hub;
    part def Device;
    connection def DeviceConn {
       end hub : Hub;
       end device : Device;
    }
}

// --- Source: Connections_1bConnectionUsage.sysml ---
package Connections_1bConnectionUsage {
    private import ScalarValues::*;
    private import SysML::*;
    part def Hub;
    part def Device;
    connection def DeviceConn { end hub : Hub; end device : Device; }
    part context {
       part hub : Hub;
       part device : Device;
       connection c1 : DeviceConn
          connect hub to device;
    }
}

// --- Source: Connections_2BindingConnector.sysml ---
package Connections_2BindingConnector {
    private import ScalarValues::*;
    private import SysML::*;
    part def A { port p1; }
    part def B { port p2; }
    part system {
       part a : A;
       part b : B;
       bind a.p1 = b.p2;
       /* CRITICAL: No array indices allowed! Bind multiple items directly: */
       /* bind a.ports = b.ports; */
    }
}

// --- Source: Connections_3InterfaceConnection.sysml ---
package Connections_3InterfaceConnection {
    private import ScalarValues::*;
    private import SysML::*;
    /* Wrapped Snippet (Structure Context) */
    interface   def  IData  {
       end  source ;
       end  target ;
       flow  source  to  target ;
    }
}

// --- Source: Connections_4SuccessionFlow.sysml ---
package Connections_4SuccessionFlow {
    private import ScalarValues::*;
    private import SysML::*;
    action process {
       action step1;
       action step2;
       first step1;
       then step2;
       doc /* Equivalent to: */
       flow from step1 to step2;
    }
}

// --- Source: Connections_Tutorial.sysml ---
package Connections_Tutorial {
    private import PortsInterfaces_Tutorial::*; /* Import Battery, Computer */
    
    part def System;
    
    part def PowerSystem :> System {
        part battery : Battery;
        part computer : Computer;
        
        /* --- Connection --- */
        /* Connecting compatible ports (PowerInterface vs ~PowerInterface) */
        connect battery.pwrPort to computer.pwrIn;
        
        /* --- Binding (Delegation) --- */
        /* Exposing the computer's ethernet port to the outside world */
        port externalEth : DataLink;
        
        /* 'bind' means internal eth0 IS the same interaction point as externalEth */
        /* MUST use '=' and NOT 'to' */
        bind externalEth = computer.eth0;
        
        /* --- Multiplicity Binding --- */
        /* Array indices are forbidden in bindings. */
        /* You can bind a single source to a multi-part target directly without indices: */
        /* bind battery.pwrOut = computers.pwrIn; */
    }
}

// --- Source: Constraints_1ConstraintDefinition.sysml ---
package Constraints_1ConstraintDefinition {
    private import ScalarValues::*;
    private import SysML::*;
    attribute def Force;
    attribute def Mass;
    attribute def Acceleration;
    constraint def NewtonLaw {
      in f : Force;
      in m : Mass;
      in a : Acceleration;
      f = m * a;
    }
}

// --- Source: Constraints_2ConstraintUsageAssert.sysml ---
package Constraints_2ConstraintUsageAssert {
    private import ScalarValues::*;
    private import SysML::*;
    attribute def Mass;
    attribute def Acceleration;
    attribute def Force;
    constraint def NewtonLaw { in f : Force; in m : Mass; in a : Acceleration; }
    part Car {
      attribute mass : Mass;
      attribute accel : Acceleration;
      attribute force : Force;
      assert constraint n1 : NewtonLaw {
        in f = force;
        in m = mass;
        in a = accel;
      }
    }
}

// --- Source: Constraints_2bInlineAssertion.sysml ---
package Constraints_2bInlineAssertion {
    private import ScalarValues::*;
    private import SysML::*;
    action def Main {
        attribute x : Integer;
        assert constraint {
           x > 0
        }
        /* Boolean expression */
    }
    view ExposeExample { expose Main; }
}

// --- Source: Constraints_3CalculationDefinition.sysml ---
package Constraints_3CalculationDefinition {
    private import ScalarValues::*;
    private import SysML::*;
    attribute def Mass;
    attribute def Speed;
    attribute def Energy;
    calc def calcKineticEnergy {
      in m : Mass;
      in v : Speed;
      return ke : Energy = 0.5 * m * v^2;
    }
}

// --- Source: Constraints_4CalculationUsage.sysml ---
package Constraints_4CalculationUsage {
    private import ScalarValues::*;
    private import SysML::*;
    attribute def Mass;
    attribute def Speed;
    attribute def Energy;
    attribute kg;
    attribute m;
    attribute s;
    calc def calcKineticEnergy { in m : Mass; in v : Speed; return ke : Energy; }
    action def Main {
        attribute kEnergy : Energy = calcKineticEnergy(m = 100 [kg], v = 20 [m/s]);
    }
    view ExposeExample { expose Main; }
}

// --- Source: CoreTypes_Tutorial.sysml ---
package CoreTypes_Tutorial {
    private import ScalarValues::*;
    
    /* --- 1. Enumerations --- */
    enum def Status {
        enum Active;
        enum Idle;
        enum Error;
    }

    /* --- 2. Attributes & Scalars --- */
    attribute def MassValue :> Real;
    
    /* --- 3. Parts (Structure) --- */
    part def StorageTank {
        attribute capacity : MassValue = 1000.0;
        attribute currentStatus : Status = Status::Idle;
    }

    /* --- 4. Items (Flow/Substance) --- */
    item def Water;
    
    part def WaterSystem {
        part tank1 : StorageTank;
        part tank2 : StorageTank;
        
        /* Items flow or are stored */
        item storedWater : Water;
    }
}

// --- Source: DataTypes_Tutorial.sysml ---
package DataTypes_Tutorial {
    private import ScalarValues::*;
    /* Note: ISQ is automatically imported by SI (public import) */
    private import SI::kg;
    private import MeasurementReferences::ConversionByPrefix;

    /* --- 1. Custom Value Definitions --- */
    /* Specializing a primitive */
    attribute def IDString :> String;
    
    /* Struct for composite data (Kernel level concept often used) */
    attribute def Coordinates {
        attribute x : Real;
        attribute y : Real;
        attribute z : Real;
    }
    
    /* --- 2. Custom Units --- */
    package ProjectUnits {
        attribute <ms> millisecond : DurationUnit {
            :>> unitConversion : ConversionByPrefix {
                :>> prefix = milli;
                :>> referenceUnit = s;
            }
        }
        attribute <'mm/h'> 'millimetre per hour' : SpeedUnit = mm / h;
    }

    part def SensorSystem {
        /* --- 3. Using Primitives --- */
        attribute isActive : Boolean = true;
        attribute firmwareVersion : String = "v1.2.4";
        attribute cycleCount : Integer = 0;
        
        /* --- 4. Using ISQ Units --- */
        /* Type checking ensures you can't assign Mass to Length */
        /* Validating physical properties (Recommended) */
        attribute weight :> ISQ::mass = 5.5 [kg];
        attribute scanRange :> ISQ::length = 150 [m];
        
        /* Raw value storage (Context-free) */
        attribute rawData : MassValue = 10.0 [kg];
        
        /* Unit conversion is handled by checks (e.g. [km] -> [m]) */
        attribute speed :> ISQ::speed = 120 [km/h]; 
        
        /* --- 5. Using Custom Types --- */
        attribute sensorID : IDString = "SENS-001";
        attribute location : Coordinates {
             :>> x = 10.0;
             :>> y = 20.0;
             :>> z = 0.0;
        }
        
        /* Information units require ISQInformation */
        attribute memorySize :> ISQInformation::storageCapacity = 64 [ISQInformation::GB];
        
        /* Battery capacity */
        attribute batteryCapacity :> ISQ::electricCharge = 1500 [ProjectUnits::mAh];
    }
}

// --- Source: DomainLibs_Tutorial.sysml ---
package DomainLibs_Tutorial {
    private import SI::m;
    private import Time::*;
    
    /* --- 1. Using ISQ Types --- */
    part def MovingObject {
        attribute mass :> ISQ::mass;
        attribute velocity :> ISQ::speed;
        attribute startingTime : TimeInstantValue;
    }
    
    part car : MovingObject {
        /* --- 2. Using Units --- */
        attribute redefines mass = 1500 [kg];
        attribute redefines velocity = 120 [km/h];
        
        /* --- 3. Time ISO 8601 --- */
        attribute redefines startingTime = "2023-10-27T10:00:00Z";
    }
    
    /* --- 4. Geometry (Shape Library) --- */
    /* (Requires Shape library import usually) */
    /* part wheel : Cylinder { */
    /*    attribute radius = 30 [cm]; */
    /* } */
}

// --- Source: Evaluation_Tutorial.sysml ---
package Evaluation_Tutorial {
    private import ScalarValues::*;
    
    /* --- 1. Calculations --- */
    calc def PowerCalc {
        in force : Real;
        in velocity : Real;
        return power : Real = force * velocity;
    }

    package System {
        part engine {
            attribute force : Real = 1000.0;
            attribute maxPower : Real = 50000.0;
            
            /* Using the calculation */
            attribute currentPower : Real = PowerCalc(force, 25.0);
        }
    }

    /* --- 2. Requirements & Constraints --- */
    requirement def PowerLimit {
        attribute actualPower : Real;
        attribute limit : Real;
        
        /* Boolean check */
        require constraint {
            actualPower <= limit
        }
    }
    
    part myEngine : System::engine {
        /* Satisfaction */
        satisfy requirement checkPower : PowerLimit {
            attribute :>> actualPower = myEngine.currentPower;
            attribute :>> limit = myEngine.maxPower;
        }
    }

    /* --- 3. Verification Case --- */
    verification def PowerTest {
        subject system : System::engine;
        
        objective {
            /* Verify that the requirement is met */
            verify checkPower {
                subject = system;
            }
        }
    }

    /* --- 4. Analysis (Trade Study) --- */
    analysis def Optimization {
        subject candidates : System::engine [1..*];
        
        objective : MaximizeObjective {
            subject;
        }
        
        /* Define how we measure 'goodness' */
        calc :>> evaluationFunction {
            in part cand :> candidates :>> alternative;
            return :>> result = cand.currentPower;
        }
    }
}

// --- Source: Features_Tutorial.sysml ---
package Feature_Tutorial_Model {
    private import ISQ::*;

    /* --- 1. Base Definitions --- */
    part def Engine {
        attribute horsepower :> ISQ::power;
        attribute mass :> ISQ::mass;
    }

    part def Wheel;

    part def Vehicle {
        part engine : Engine[1];
        part wheels : Wheel[4];
    }

    /* --- 2. Subsetting Example --- */
    part def Truck :> Vehicle {
        /* 'front' and 'rear' partition the 'wheels' set */
        part frontWheels[2] subsets wheels;
        part rearWheels[2] subsets wheels;
    }

    /* --- 3. Redefinition Example --- */
    part def ElectricMotor :> Engine;
    
    part def ElectricCar :> Vehicle {
        /* Replace generic Engine with ElectricMotor */
        part redefines engine : ElectricMotor;
    }

    /* --- 4. Feature Chaining & Redeclaration Example --- */
    part def SportsCar :> Vehicle {
        /* Feature Chaining: reaching into 'engine' */
        /* Redeclaration (:>>) shorthand for 'redefines' or 'subsets' */
        
        attribute :>> engine.horsepower = 500 [hp];
        
        /* This is structurally equivalent to: */
        /* part :>> engine { */
        /* attribute :>> horsepower = 500 [hp]; */
        /*  */}
    }
}

// --- Source: Filters_Tutorial.sysml ---
package Filters_Tutorial {
    private import DS_Views::SymbolicViews;
    private import Metaobjects::SemanticMetadata;
    
    part def HardwareComponent;
    part def SoftwareComponent;
    
    metadata def Critical;
    
    part system {
        part cpu : HardwareComponent;
        
        @Critical
        part os : SoftwareComponent;
        
        part driver : SoftwareComponent;
    }
    
    /* --- 1. Filtering by Type --- */
    view hardwareView : SymbolicViews::gv {
        expose system::**;
        
        /* Only show HardwareComponents */
        filter hastype HardwareComponent;
    }
    
    /* --- 2. Filtering by Metadata (Stereotypes) --- */
    view criticalView : SymbolicViews::gv {
        expose system::**;
        
        /* Only show elements tagged as @Critical */
        filter @Critical;
    }
    
    /* --- 3. Complex Logic --- */
    view complexView : SymbolicViews::gv {
        expose system::**;
        
        /* Show Software that is NOT Critical */
        filter hastype SoftwareComponent and not @Critical;
    }
}

// --- Source: Flows_Tutorial.sysml ---
package Flows_Tutorial {
    private import ScalarValues::*;
    
    item def Fuel;
    
    part def Tank;
    part def Engine;
    
    part def FuelSystem {
        part t : Tank;
        part e : Engine;
        
        /* --- Explicit Item Flow --- */
        /* Declaring that Fuel moves from Tank to Engine */
        /* This implies a connection exists or is abstractly represented */
        flow of Fuel from t to e;
        
        /* --- Connector with Flow --- */
        connect t to e {
            /* Optional property on the flow */
            flow of Fuel from t to e {
                attribute rate : Real = 5.0;
            }
        }
    }
}

// --- Source: Metadata_1MetadataDefinition.sysml ---
package Metadata_1Definition {
    private import ScalarValues::*;
    private import SysML::*;
    doc /* Define custom metadata (like a Stereotype) */
    metadata def Risk {
        attribute level : Integer;
        attribute desc : String;
    }
}

// --- Source: Metadata_2ElementAnnotation.sysml ---
package Metadata_2ElementAnnotation {
    private import ScalarValues::*;
    private import SysML::*;
    metadata def Risk { attribute level : Integer; attribute desc : String = ""; }
    
    doc /* Usage within element */
    part engine {
        metadata Risk {
            :>> level = 5;
            :>> desc = "Overheat potential";
        }
    }
    
    doc /* Shorthand annotation nested in definition */
    part wheel {
        @Risk { :>> level = 1; }
    }
}

// --- Source: Metadata_3RelationshipAnnotation.sysml ---
package Metadata_3RelationshipAnnotation {
    private import ScalarValues::*;
    private import SysML::*;
    metadata def RefineData { attribute isRefine : Boolean; }
    requirement req1;
    requirement req2;
    
    doc /* Annotating a dependency */
    dependency from req2 to req1 {
        metadata RefineData {
            :>> isRefine = true;
        }
    }
}

// --- Source: Metadata_4StandardMetadata.sysml ---
package Metadata_4Standard {
    private import ScalarValues::*;
    private import SysML::*;
    
    doc /* Deprecation */
    part oldPart {
        @Deprecated;
    }
    
    metadata def FIXME;
    
    action check {
        @FIXME {
            doc /* Needs update */
        }
    }
}

// --- Source: Metadata_5MetadataExtension.sysml ---
package Metadata_5Extension {
    private import ScalarValues::*;
    private import SysML::*;
    
    doc /* Base metadata */
    metadata def TestPlan {
        attribute tool : String;
    }
    
    doc /* Extended metadata (Inheritance) */
    metadata def LabTest :> TestPlan {
        attribute labId : String;
    }
    
    metadata def VRTest :> TestPlan {
        attribute headsetModel : String;
    }
    
    doc /* Usage with values */
    action runUnitTests {
        @LabTest {
            :>> tool = "JUnit";
            :>> labId = "Lab-101";
        }
    }
    
    action runSimTest {
        @VRTest {
            :>> tool = "Unity";
            :>> headsetModel = "Quest 3";
        }
    }
}

// --- Source: Metadata_6ShortAnnotation.sysml ---
package Metadata_6Hashtags {
    private import ScalarValues::*;
    private import SysML::*;
    
    package Vehicle_Metadata {
        metadata def Vehicle;
        metadata def Engine;
        metadata def Wheel;
    }
    package Car_Example {
        private import Vehicle_Metadata::*;
        
        #Vehicle def Car {
            #Engine part carEngine [1];
            #Wheel part carWheels [4];
        }
    }
}

// --- Source: Multiplicity_Tutorial.sysml ---
package Multiplicity_Tutorial {
    
    part def Person;
    part def Wheel;
    
    /* --- 1. Package Context --- */
    /* Usage directly in package defaults to [0..*] */
    part looseWheels : Wheel; 

    part def Car {
        /* --- 2. Definition Context --- */
        /* Usage in a definition (part/attr/port) defaults to [1] */
        part engine : Person; /* [1..1] Required */
        
        /* --- Explicit Constraints --- */
        part wheels : Wheel [4]; /* Exactly 4 */
        
        /* --- 3. Inheritance --- */
        /* subsets: inherits parent multiplicity (here [1]) */
        /* We can constrain it further, or leave it. */
        part driver subsets engine; 
        
        /* --- 4. Collections --- */
        /* unique (Default): Set */
        part passengers : Person [0..4]; 
        
        /* ordered nonunique: Sequence */
        attribute lapTimes : ScalarValues::Real [*] ordered nonunique;
    }
    
    action def Drive {
        /* Default parameter multiplicity is [1] */
        in distance : ScalarValues::Integer; 
    }
}

// --- Source: Naming_Tutorial.sysml ---
package Naming_Tutorial {
    private import ScalarValues::*;
    
    /* --- Library Definitions --- */
    package StandardLibrary {
        part def Widget;
        part def Gadget;
        attribute def Status;
    }
    
    package SpecializedLibrary {
        /* Name collision with StandardLibrary */
        part def Widget; 
    }

    /* --- Imports & Aliasing --- */
    /* Public import: 'StandardLibrary' is visible to users of 'Naming_Tutorial' */
    /* Real-world example: The 'SI' library has 'public import ISQ::*;' */
    public import StandardLibrary::*;
    
    /* Private import: Resolving collision with alias */
    private import SpecializedLibrary::Widget as SpecialWidget;

    /* --- Definitions & Usages --- */
    part def SystemContext {
        /* Usage of standard import */
        part standardPart : Widget;
        
        /* Usage of aliased element */
        part specialPart : SpecialWidget;
        
        /* Using the alias defined in the package */
        alias SW for SpecialWidget;
        part anotherPart : SW;
        
        /* Escaped identifier for spaces */
        attribute 'System ID' : String;
        
        /* Correct Convention: camelCase usage */
        part mainGadget : Gadget;
        
        /* Unit reference uses brackets, no quotes needed for special chars */
        attribute speed : Real [km/h];
    }
}

// --- Source: PartsAndAttributes_Tutorial.sysml ---
package PartsAndAttributes_Tutorial {
    private import ISQ::*; /* Import standard quantities */
    
    /* --- Definitions --- */
    part def Engine {
        attribute maxThrust :> ISQ::force;
        attribute mass :> ISQ::mass;
    }
    
    part def FuelTank {
        attribute capacity : VolumeValue;
    }
    
    /* --- Composite Definition --- */
    part def Spacecraft {
        /* Attributes of the spacecraft itself */
        attribute totalMass :> ISQ::mass;
        attribute callSign : String;
        
        /* Parts (Usages */)
        /* Decomposing Spacecraft into subsystems */
        part mainEngine : Engine {
            /* Assigning values to attributes */
            attribute :>> maxThrust = 500 [kN];
            attribute :>> mass = 1000 [kg];
        }
        
        part reserveEngine : Engine; /* Uses defaults if any */
        
        part fuelSystem {
            part loxTank : FuelTank;
            part rp1Tank : FuelTank;
        }
    }
    
    /* --- Concrete Instance --- */
    part myShip : Spacecraft {
        attribute :>> callSign = "Voyager-1";
    }
}

// --- Source: Patterns_1MetadataAnnotations.sysml ---
package Patterns_1MetadataAnnotations {
    private import ScalarValues::*;
    private import SysML::*;
    /* Wrapped Snippet (Structure Context) */
    metadata   def  Status  {
      attribute  priority  :  Integer ;
      attribute  approved  :  Boolean ;
    }
    part  myPart  {
      metadata  Status  {
        priority  =  1 ;
      }
    }
}

// --- Source: Patterns_2Views.sysml ---
package Patterns_2Views {
    private import ScalarValues::*;
    private import SysML::*;
    part def GeneralDiagram;
    /* Wrapped Snippet (Structure Context) */
    view  MyView  :  GeneralDiagram  {
    /* filter Status; */
    }
    /* Rendering specific subsets */
}

// --- Source: Patterns_3CustomUnitsNanoBanana.sysml ---
package BananaUnits {
    private import ScalarValues::*;
    private import SysML::*;
    attribute def LengthUnit {
        attribute prefix;
        attribute referenceUnit;
    }
    attribute nano;
    attribute <nB> nanoBanana : LengthUnit {
        attribute unitConversion;
        :>> prefix = nano;
        :>> referenceUnit = "Standard Banana";
    }
}

// --- Source: Patterns_4AbstractvsIndividual.sysml ---
package Patterns_4AbstractvsIndividual {
    private import ScalarValues::*;
    private import SysML::*;
    /* Wrapped Snippet (Structure Context) */
    abstract  part  def  Wheel ;
    part  def  Bus  {
      abstract  part  wheel  [4]  :  Wheel ;
    }
    individual  part  myBus  :  Bus  {
      part  frontLeft  :>  wheel ;
    }
}

// --- Source: PortsInterfaces_Tutorial.sysml ---
package PortsInterfaces_Tutorial {
    private import ScalarValues::*;
    
    /* --- 1. Interface Definitions --- */
    /* Physical connection interface */
    interface def PowerInterface {
        /* 'out' means power leaves this port locally */
        out powerLevel : Real;
    }
    
    /* Logical data interface */
    interface def DataLink {
        /* end definitions MUST be typed by a port (if complex) or left untyped */
        end source;
        end target;
        /* flow of messages inside the interface */
        flow source to target;
        /* CRITICAL: do not use 'from' or 'of' inside interface flows */
    }

    /* --- 2. Component Definitions --- */
    part def Battery {
        /* Provides power (Source) */
        port pwrPort : PowerInterface;
    }

    part def Computer {
        /* Consumes power (Sink) */
        /* '~' (Tilde) conjugates the interface: 'out' becomes 'in' */
        port pwrIn : ~PowerInterface;
        
        /* Data port */
        port eth0 : DataLink;
    }
}

// --- Source: Reference_1CommonKeywords.sysml ---
package Reference_1CommonKeywords {
    doc /*
      package, import, private import
      attribute def, attribute
      part def, part
      action def, action
      item def, item
      state def, state
      interface def, port def, port
      connection def, connection
      requirement def, requirement
      constraint def, constraint, assert
      analysis def, analysis
      verification def, verification
      view def, view
      metadata def, metadata
    */
}

// --- Source: Reference_2PrimitiveTypes.sysml ---
package Reference_2PrimitiveTypes {
    private import ScalarValues::*;
    private import Base::*;
    private import SysML::*;
    attribute b : Boolean; /* true, false */
    attribute i : Integer; /* 1, -5, 0 */
    attribute r : Real; /* 3.14, 1.0 */
    attribute s : String; /* 'text' */
    attribute n : Natural; /* 0, 1, * (UnlimitedNatural in v1 */)
}

// --- Source: Reference_3Relationships.sysml ---
package Reference_3Relationships {
    doc /*
      Generalization ( :> ) - Inheritance
      Subsetting ( :> ) - Hierarchy
      Redefinition ( :>> ) - Specialized replacement
      Reference ( references ) - Pointer
      Conjugation ( ~ ) - Reverse port
      Binding ( = ) - Equality
      Assignment ( := ) - Value set
      Succession ( first..then ) - Ordering
    */
}

// --- Source: Reference_4Comments.sysml ---
package Reference_4Comments {
    /* Single line */
    /* Multi-line
       comment */
    doc /* Documentation */
    /* Single line */
    /* Multi-line
       comment */
    doc /* Documentation */
    part element;
    comment about element /* text */
}

// --- Source: Reference_5Multiplicity.sysml ---
package Reference_5Multiplicity {
    doc /*
      [1]      - Exactly one (Default)
      [0..1]   - Optional
      [*]      - Zero or more
      [1..*]   - One or more
      [2..5]   - Specific range
    */
}

// --- Source: Reference_6Visibility.sysml ---
package Reference_6Visibility {
    doc /*
      public    (default) - Visible everywhere
      private   (private) - Visible only inside
      protected (protected) - Visible to children
    */
}

// --- Source: Requirements_1RequirementDefinition.sysml ---
package Requirements_1RequirementDefinition {
    private import ScalarValues::*;
    private import SysML::*;
    attribute def Time;
    requirement def Performance {
      doc /* The system shall be fast. */
      attribute maxResponse : Time;
    }
}

// --- Source: Requirements_2RequirementUsage.sysml ---
package Requirements_2RequirementUsage {
    private import ScalarValues::*;
    private import SysML::*;
    attribute def Time;
    attribute ms;
    requirement def Performance { attribute maxResponse : Time; }
    requirement <'REQ-001'> 'Fast' : Performance {
      doc /* Response < 10ms */
      attribute maxResponse = 10 [ms];
    }
}

// --- Source: Requirements_3Satisfy.sysml ---
package Requirements_3Satisfy {
    private import ScalarValues::*;
    private import SysML::*;
    requirement def Performance;
    requirement req1 : Performance;
    part server {
      satisfy req1;
    }
    /* satisfy req1 by server; // Alternative syntax */
}

// --- Source: Requirements_4Verify.sysml ---
package Requirements_4Verify {
    private import ScalarValues::*;
    private import SysML::*;
    requirement req1;
    verification def TestLatency {
      objective {
          verify req1;
      }
    }
}

// --- Source: Requirements_5ConstraintDefinition.sysml ---
package Requirements_5ConstraintDefinition {
    private import ScalarValues::*;
    private import SysML::*;
    attribute def Mass;
    attribute kg;
    constraint def CheckMass {
      in m : Mass;
      m <= 1000 [kg]
    }
}

// --- Source: Requirements_6AssertConstraint.sysml ---
package Requirements_6Assertions {
    private import ScalarValues::*;
    private import SysML::*;
    attribute def Mass;
    attribute kg;
    part car {
      attribute mass : Mass;
      require constraint {
        mass <= 1000 [kg]
      }
    }
}

// --- Source: Requirements_7TraceRefine.sysml ---
package Requirements_7TraceRefine {
    private import ScalarValues::*;
    private import SysML::*;
    requirement req1;
    requirement old_doc_item;
    requirement req2 {
      doc /* Using dependency to represent relationships */
      dependency from req2 to req1;
      dependency from req2 to old_doc_item;
    }
}

// --- Source: Requirements_Tutorial.sysml ---
package Requirements_Tutorial {
    private import ScalarValues::*;
    
    /* --- 1. Requirements --- */
    requirement def PerformanceReq {
        doc /* Textual description */
            "The system shall operate within performance limits.";
    }
    
    requirement <'REQ-101'> 'Breaking Distance' : PerformanceReq {
        doc /* The vehicle must stop within 50 meters from 100km/h. */
        /* Formal attributes */
        attribute maxDistance : Real = 50.0;
        attribute actualDistance : Real;
        /* Formal constraint (CRITICAL: no semicolon after constraint block) */
        require constraint {
            actualDistance <= maxDistance
        }
    }

    /* --- 2. Satisfaction (Design) --- */
    part def BrakeSystem;
    
    part brakes : BrakeSystem {
        /* Asserting that this part satisfies the requirement */
        satisfy 'Breaking Distance';
    }
    
    /* --- 3. Verification (Testing) --- */
    /* A case to test the requirement */
    verification def BrakeTest {
        /* The requirement being verified */
        subject req : PerformanceReq;
        
        /* The logic (action) of the test */
        action executeTest {
            /* ... test steps ... */
        }
    }
    
    /* Usage of validation */
    verification case test1 : BrakeTest {
        verify 'Breaking Distance';
    }
}

// --- Source: SemanticMetadata_Tutorial.sysml ---
package DroneDSLinSysML {
    
    /* --- 1. Domain Library (Vocabulary) --- */
    library package Drone_Library {
        part def Sensor;
        part def ImageSensor :> Sensor;
        part def CollisionSensor :> Sensor;
        
        part def Rotor;
        
        part def Drone {
           part rotors : Rotor [1..*];
           part sensors : Sensor [0..*];
        }
    }
    
    /* --- 2. Metadata Definitions (The Mapping) --- */
    package Drone_Metadata {
        private import Drone_Library::*;
        private import Metaobjects::SemanticMetadata;
        
        metadata def drone :> SemanticMetadata {
            :>> baseType = Drone meta SysML::Definition;
            :> annotatedElement : SysML::Definition;
        }
        
        metadata def rotor :> SemanticMetadata {
            :>> baseType = Rotor meta SysML::Usage;
            :> annotatedElement : SysML::Usage;
        }
        
        metadata def cam :> SemanticMetadata {
            :>> baseType = ImageSensor meta SysML::Usage;
            :> annotatedElement : SysML::Usage;
        }
        
        metadata def lidar :> SemanticMetadata {
            :>> baseType = CollisionSensor meta SysML::Usage;
            :> annotatedElement : SysML::Usage;
        }
    }
    
    /* --- 3. DSL Usage (The Result) --- */
    package Mission_Model {
        private import Drone_Metadata::*;
        
        #drone part def SurveillanceDrone {
            /* Using the DSL vocabulary: */
            #rotor part frontRotors[2];
            #rotor part rearRotors[2];
            
            /* Defining sensors using shorthand */
            #cam part mainCamera;
            #lidar part obstacleAvoider;
        }
    }
}

// --- Source: Shorthand_1Specialization.sysml ---
package Shorthand_1Specialization {
    private import ScalarValues::*;
    private import SysML::*;
    part def Vehicle;
    /* Wrapped Snippet (Structure Context) */
    part  def  Car  :>  Vehicle ;
    doc  /* Equivalent to: 
            part  def  Car  specializes  Vehicle ; */
}

// --- Source: Shorthand_2Subsetting.sysml ---
package Shorthand_2Subsetting {
    private import ScalarValues::*;
    private import SysML::*;
    part parts;
    /* Wrapped Snippet (Structure Context) */
    part  engine  :>  parts ;
    doc  /* Equivalent to: 
            part  engine  subsets  parts ; */
}

// --- Source: Shorthand_3Redefinition.sysml ---
comment about Shorthand_3Redefinition /* Source: Shorthand_3Redefinition.sysml */
package Shorthand_3Redefinition {
    private import ISQ::*;
    comment /* Wrapped Snippet (Structure Context)
    attribute partMass : ISQBase::mass  =  100.0 ;
    attribute partMass1 :>> partMass  =  101.0 ;   
    attribute  partMass2 redefines  partMass  =  101.0 ;
    comment about partMass1, partMass2 /* :>> and redefines are equivelnt */
}

// --- Source: Shorthand_4Conjugation.sysml ---
package Shorthand_4Conjugation {
    private import ScalarValues::*;
    private import SysML::*;
    port def Interface;
    /* Wrapped Snippet (Structure Context) */
    port  p  :  ~ Interface ;
    doc  /* Equivalent to: 
            port  p  :  conjugated  Interface ; */
}

// --- Source: Shorthand_5FeatureValues.sysml ---
package Shorthand_5FeatureValues {
    private import ScalarValues::*;
    private import SysML::*;
    /* Wrapped Snippet (Structure Context) */
    attribute  x  =  1 ;  /* Binding (Equality) */
    attribute  y  :=  2 ;  /* Initial Value */
    attribute  z  default  =  3 ;  /* Default Value */
}

// --- Source: Shorthand_6Multiplicity.sysml ---
package Shorthand_6Multiplicity {
    private import ScalarValues::*;
    private import SysML::*;
    /* Wrapped Snippet (Structure Context) */
    part  many [*] ;  /* 0..* */
    part  one ;  /* 1..1 (Default) */
    part  opt [0..1] ;  /* 0..1 */
}

// --- Source: StateMachine_Tutorial.sysml ---
package StateMachine_Tutorial {
    private import SI::s;
    
    /* Define the component containing the machine */
    part def TrafficLight {
        /* Local actions defined in part scope can access part attributes */
        action def LogStatus;
        
        /* The machine behavior */
        state def LightLogic {
            /* Initial entry point */
            entry;
            then Red;
            
            state Red;
            state Yellow;
            state Green;
            
            transition redToGreen first Red accept after 20 [SI::s] then Green;
            transition greenToYellow first Green accept after 5 [SI::s] then Yellow;
            /* Using if-guard and do-action */
            transition yellowToRed first Yellow accept after 30 [SI::s] if true do action log : LogStatus then Red;
        }
        /* Usage of the machine */
        state logic : LightLogic;
    }
    view StateMachine_Tutorial : DS_Views::SymbolicViews::gv;
}

// --- Source: StatePatterns_1EntryDoExit.sysml ---
package StatePatterns_1EntryDoExit {
    private import ScalarValues::*;
    private import SysML::*;
    action def logStart;
    action def maintain;
    action def logEnd;
    state def Active {
       entry action : logStart;
       do action : maintain;
       exit action : logEnd;
    }
}

// --- Source: StatePatterns_2CompositeState.sysml ---
package StatePatterns_2CompositeState {
    private import ScalarValues::*;
    private import SysML::*;
    state def Composite {
       entry;
       state Sub1;
       state Sub2;
       transition t1
          first Sub1
          then Sub2;
    }
}

// --- Source: StatePatterns_3ExhibitState.sysml ---
package StatePatterns_3ExhibitState {
    private import ScalarValues::*;
    private import SysML::*;
    state def VehicleStates { state operating; }
    part def Vehicle {
       exhibit state opState : VehicleStates;
    }
}

// --- Source: StatePatterns_4InternalTransition.sysml ---
package StatePatterns_4InternalTransition {
    private import ScalarValues::*;
    private import SysML::*;
    action def tick;
    action check;
    state def Monitoring {
       state Idle;
       /* Internal behavior (Self-transition */)
       transition t1 first Idle accept tick do check then Idle;
    }
}

// --- Source: States_1StateDefinition.sysml ---
package States_1StateDefinition {
    private import ScalarValues::*;
    private import SysML::*;
    /* Wrapped Snippet (Structure Context) */
    action def logStart;
    action def logEnd;
    state   def  TrafficLight  {
       entry  action : logStart ;
       exit   action : logEnd ;
       state  Red ;
       state  Green ;
    }
}

// --- Source: States_2Transitions.sysml ---
package States_2Transitions {
    private import ScalarValues::*;
    private import SysML::*;
    state def Main {
        state Red;
        state Green;
        action def TimeEvent;
        transition t1
           first Red
           accept TimeEvent
           then Green;
    }
}

// --- Source: States_3GuardsEffects.sysml ---
package States_3GuardsEffects {
    private import ScalarValues::*;
    private import SysML::*;
    state def Main {
        state Green;
        state Red;
        attribute traffic : Integer;
        action resetTimer;
        transition t2
           first Green
           if traffic == 0
           do resetTimer
           then Red;
    }
}

// --- Source: States_4CompositeStates.sysml ---
package States_4CompositeStates {
    private import ScalarValues::*;
    private import SysML::*;
    /* Wrapped Snippet (Structure Context) */
    state Operational {
       entry;
       state Normal;
       state Maintenance;
    }
}

// --- Source: States_5ParallelStates.sysml ---
package States_5ParallelStates {
    private import ScalarValues::*;
    private import SysML::*;
    /* Wrapped Snippet (Structure Context) */
    state def System parallel {
       state Power;
       state Connectivity;
    }
}

// --- Source: UseCaseTutorial_APS.sysml ---
package AutomatedPickleballServerModel {


    /* --- Definitions --- */
    part def ActorPart;
    use case def TrackPlayerState;
    use case def DetermineNextShot;
    use case def ServeBall;

    /* --- 1. Define the Actors --- */
    part def Player :> ActorPart;
    part def CourtEnvironment :> ActorPart;

    /* --- 2. Define the Subject System --- */
    part def AutomatedPickleballServer {
      part aiController;
      part ballLauncher;
      part sensorSuite;
    }

    /* --- 3. Define the Use Cases --- */
    use case def PlayPracticeSession {
      subject aps : AutomatedPickleballServer;
      actor player : Player;

      doc /* The player engages in a practice session where the server
             serves balls tailored to their skill level. */

      /* This use case INCLUDES other core behaviors */
      include use case trackPlayer : TrackPlayerState;
      include use case determineShot : DetermineNextShot;
      include use case serveBall : ServeBall;
    }
}


// --- Source: Variants_Tutorial.sysml ---
package Variants_Tutorial {
    
    /* abstract definition */
    part def Engine;
    
    /* --- 1. Variants --- */
    part def V6Engine :> Engine;
    part def V8Engine :> Engine;
    part def ElectricMotor :> Engine;
    
    /* --- 2. Variation Point --- */
    part def Car {
        /* 'variation' declares this must be chosen */
        variation part engine : Engine;
    }
    
    /* --- 3. Configuration (Binding) --- */
    /* A specific configuration of the Car */
    part def SportCar :> Car {
        /* Binding the variation point to a specific type */
        variant part redefines engine : V8Engine;
    }
    
    part def EcoCar :> Car {
        variant part redefines engine : ElectricMotor;
    }
}

// --- Source: Viewpoints_Tutorial.sysml ---
package Viewpoint_Tutorial {
    private import ScalarValues::*;
    
    /* The subject */
    part def Car {
        attribute mass : Real;
        part engine;
        part wheels;
    }
    
    /* --- 1. Viewpoint Definition --- */
    viewpoint def MassReport {
        doc "A report focusing only on mass properties.";
    }
    
    /* --- 2. Viewpoint Usage --- */
    viewpoint <'VP-002'> 'mass report viewpoint' : MassReport {
        doc "Focuses on mass properties of the vehicle";
    }
    
    /* --- 3. View Definition --- */
    view def MassView {
        /* The subject being viewed */
        in car : Car;
        
        /* --- 4. Exposing Elements --- */
        /* Show the car itself */
        expose car;
        
        /* Show sub-parts */
        expose car.engine;
        
        /* Filter: Only show attributes ending in 'Mass' (conceptual) */
        /* filter @Attribute ==> name.endsWith("sw") */
    }
    
    /* --- 5. View Usage --- */
    part myCar : Car;
    
    view report : MassView {
        in car = myCar;
        satisfy 'mass report viewpoint';
    }
}

// --- Source: Views_Sheet_1ViewDefinition.sysml ---
package Views {
    part def System;
    
    view def ReportView {
        /* Input parameter for subject */
        in subject : System;
    }
}

// --- Source: Views_Sheet_2ViewUsage.sysml ---
package Views {
    part def System;
    part mySystem : System; 
    view def ReportView { in subject : System; }
    
    /* View Usage */
    view report : ReportView {
        in subject = mySystem;
    }
}

// --- Source: Views_Sheet_3Viewpoint.sysml ---
package Views {
    /* 1. Define specific concern/perspective */
    viewpoint def SafetyAnalysis {
        doc "Focus on hazards.";
    }
    
    /* 2. Create viewpoint usage */
    viewpoint <'vp1'> 'sa' : SafetyAnalysis;
    
    /* 3. Link view usage to viewpoint usage */
    view mySafetyView {
        satisfy 'sa';
    }
}

// --- Source: Views_Sheet_4ExposeContent.sysml ---
package Views {
    part def Car { part engine; part wheels[4]; }
    part myCar : Car;
    
    view myView {
        /* Expose specific element */
        expose myCar;
        
        /* Expose element and all children recursively */
        expose myCar::**; 
    }
}

// --- Source: Views_Sheet_5Filter.sysml ---
package Views {
    private import ScalarValues::*;
    part def Car;
    part myCar : Car;
    
    view myView {
        expose myCar::**;
        
        /* Keep only Parts */
        filter @PartUsage;
        
        /* Keep only Allocations (CRITICAL: use Usage, not Definition) */
        filter @AllocationUsage;
        
        /* Or exclude specific things (logic depends on library) */
    }
}

// --- Source: Views_Sheet_6RenderingStyle.sysml ---
package Views {
    /* Assuming standard libraries available */
    view def MyView {
        /* Apply visual style */
        style color = "blue";
        
        /* Define table structure */
        render asTable {
           /* table details */
        }
    }
}

// --- Source: Views_Tutorial.sysml ---
package Views_Tutorial {
    /* Import Cameo View Libraries */
    private import DS_Views::SymbolicViews;
    private import DS_Views::TabularViews;
    private import SysML::Systems::*;
    
    package <BV> BaseViews {
        view partsTreeView : TreeView, EssentialElementsFilter, NonStandardLibraryElementFilter {
            filter @PartDefinition;
            filter @PartUsage;
        }
        view allocationTableView : rt, EssentialElementsFilter, NonStandardLibraryElementFilter {
            /* CRITICAL: use @AllocationUsage, not @Allocation */
            filter @AllocationUsage;
        }
    }

    part def Car;
    part def Engine;
    part def Wheel;
    
    part myCar : Car {
        part engine : Engine;
        part wheels [4] : Wheel;
    }
    
    /* --- 1. Graphical View (Diagram) --- */
    view carDiagram : SymbolicViews::gv, EssentialElementsFilter, NonStandardLibraryElementFilter {
        /* Show the entire car structure */
        expose myCar;
        
        /* You can filter or refine what is shown here */
        /* (See Filters Tutorial) */
    }
    
    /* --- 2. Tabular View (Table) --- */
    /* Defining a reusable table structure */
    view def PartTable :> TabularViews::gt {
        /* Define columns */
        render rendering :>> asTable {
            view :>> 'Declared Name';
            view :>> 'Owner';
        }
    }
    
    /* Using the table */
    view myTable : PartTable {
        /* Show everything under myCar recursively */
        expose myCar::**;
    }
}
