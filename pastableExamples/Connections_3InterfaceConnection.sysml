package Connections_3InterfaceConnection {
    private import ScalarValues::*;
    private import SysML::*;
    /* Wrapped Snippet (Structure Context) */
    interface   def  IData  {
       end  source ;
       end  target ;
       flow  source  to  target ;
    }
}
