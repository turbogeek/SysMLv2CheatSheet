package Shorthand_4Conjugation {
    private import ScalarValues::*;
    private import SysML::*;
    // Wrapped Snippet (Structure Context)
    port p : ~Interface;
    doc /* Equivalent to: */
    port p : conjugated Interface;
}
