package Connections_1bConnectionUsage {
    private import ScalarValues::*;
    private import SysML::*;
    // Wrapped Snippet (Structure Context)
    part context {
       connection c1 : DeviceConn
          connect hub to device;
    }
}
