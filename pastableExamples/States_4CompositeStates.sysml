package States_4CompositeStates {
    private import ScalarValues::*;
    private import SysML::*;
    /* Wrapped Snippet (Structure Context) */
    state Operational {
       entry;
       state Normal;
       state Maintenance;
    }
}
