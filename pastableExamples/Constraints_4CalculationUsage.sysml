package Constraints_4CalculationUsage {
    private import ScalarValues::*;
    private import SysML::*;
    // Wrapped Snippet (Structure Context)
    attribute kEnergy = calcKineticEnergy(
      m = 100[kg],
      v = 20[m/s]
    );
    /* Result assigned to attribute */
}
