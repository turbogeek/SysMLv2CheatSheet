package Views {
    /* Assuming standard libraries available */
    view def MyView {
        /* Define table structure */
        render rendering asTable {
           /* table details */
        }
    }
}
