package States_5ParallelStates {
    private import ScalarValues::*;
    private import SysML::*;
    /* Wrapped Snippet (Structure Context) */
    state def System parallel {
       state Power;
       state Connectivity;
    }
}
